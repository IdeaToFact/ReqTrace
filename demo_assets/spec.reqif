## obj_001
The aircraft flight control computer shall maintain state estimation during sensor failover.
- Customer_Req_Number: SYS-NAV-001
- Requirement Level: System
- Object Type: Requirement

## obj_002
The navigation system shall switch to inertial dead-reckoning within 200ms of GPS loss.
- Customer_Req_Number: REQ-NAV-0104
- Requirement Level: High-Level
- Object Type: Requirement
- links to -> obj_001

## obj_003
Backup battery supply shall sustain avionics bus power for at least 30 minutes.
- Customer_Req_Number: REQ-PWR-002
- Requirement Level: Low-Level
- Object Type: Requirement
