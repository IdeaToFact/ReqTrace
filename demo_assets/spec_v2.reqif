## obj_001
The aircraft flight control computer shall maintain state estimation during sensor failover.
- Customer_Req_Number: SYS-NAV-001
- Requirement Level: System
- Object Type: Requirement

## obj_002
The navigation system shall switch to inertial dead-reckoning within 100ms of GPS loss.
- Customer_Req_Number: REQ-NAV-0104
- Requirement Level: High-Level
- Object Type: Requirement
- links to -> obj_001

## obj_004
All flight logs shall be cryptographically signed using SHA-256 before telemetry transmission.
- Customer_Req_Number: REQ-SEC-001
- Requirement Level: High-Level
- Object Type: Requirement
