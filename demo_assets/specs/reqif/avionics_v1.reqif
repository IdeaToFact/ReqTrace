## obj_sec_01: Section 1: Flight Control and Avionics Scope
Informative scope overview for Flight Control Suite Rev 1.0.
- Customer_Req_Number: SEC-01
- Object Type: Heading
- Requirement Level: System

## obj_sys_001: Triple-Modular IMU Failover
The flight control computer shall maintain triple-modular redundant attitude estimation during single IMU failure.
- Customer_Req_Number: SYS-FLT-001
- Object Type: Requirement
- Requirement Level: System

## obj_nav_101: GPS Loss Dead-Reckoning Switchover
The navigation subsystem shall switch to inertial dead-reckoning within 200ms of GPS signal loss.
- Customer_Req_Number: REQ-NAV-101
- Object Type: Requirement
- Requirement Level: High-Level
- links to -> obj_sys_001

## obj_nav_102: Kalman Position Drift Ceiling
Kalman filter position drift shall remain below 5.0 meters over any 60-second dead-reckoning interval.
- Customer_Req_Number: REQ-NAV-102
- Object Type: Requirement
- Requirement Level: High-Level
- links to -> obj_sys_001

## obj_pwr_201: Emergency Battery Bus Sustain
Emergency backup battery shall sustain primary avionics bus voltage above 24.0V for at least 30 minutes.
- Customer_Req_Number: REQ-PWR-201
- Object Type: Requirement
- Requirement Level: Low-Level

## obj_com_301: ARINC-429 Bus Overload Shedding
ARINC-429 telemetry bus scheduler shall drop non-critical frames when bus utilization exceeds 85 percent.
- Customer_Req_Number: REQ-COM-301
- Object Type: Requirement
- Requirement Level: Low-Level

## obj_hyd_401: Hydraulic Actuator Bypass Protection
Hydraulic actuator servo loop shall detect pressure drop below 1800 PSI and engage bypass valve within 50ms.
- Customer_Req_Number: REQ-HYD-401
- Object Type: Requirement
- Requirement Level: High-Level

## obj_orphan_900: Crash Memory AES-256 Encryption
Cockpit flight data recorder shall encrypt solid-state crash memory using AES-256-GCM at rest.
- Customer_Req_Number: REQ-ORPHAN-900
- Object Type: Requirement
- Requirement Level: Low-Level
